-- *****************************************************************************
-- Copyright (c) 2020  Ericsson AB
-- All rights reserved. This program and the accompanying materials
-- are made available under the terms of the Eclipse Public License v2.0
-- which accompanies this distribution, and is available at
-- https://www.eclipse.org/org/documents/epl-2.0/EPL-2.0.html
--
-- Contributors:
--   Gabor Szalai - initial implementation and initial documentation
-- *****************************************************************************/
--
--  File:               JWS_helper.asn
--  Description:	      Type definitions for JWS, PASSporT and SHAKEN
-- ///////////////////////////////////////////// 
JWS-helper 

DEFINITIONS


::=

BEGIN

IMPORTS;

JWS-helper-struct ::= SEQUENCE {
  f1 INTEGER,
  f2 INTEGER
}

END
